module shaper {
         
         namespace "http://www.comics.unina.it/nc/simpleHost";
         prefix "shost";

         organization "COMICS at Unina Inc.";
         contact "comics@comics.unina.it";
         description
             "Simple module for for configuring IP addresses of the interfaces of a Linux host.";

         revision 2013-01-01 {
             description "Initial revision.";
         }

         container simpleHost {

	  
	    list interface {
	      key "name";
	      
	      leaf name {
		type string;
	      }
         
	      leaf ipv4_address {
		type string;
	      }
	      
	      leaf ipv6_address {
		type string;
	      }
	    }
	  }
	  
    }
